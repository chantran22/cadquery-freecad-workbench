import cadquery as cq

r = cq.Workplane("front").circle(2.0).extrude(0.15) 
                          # make base
#r = r.pushPoints([(1.5, 0), (0, 1.5), (-1.5, 0), (0, -1.5)])    # now four points are on the stack
#r = r.circle(0.25)                                              # circle will operate on all four points
#r1 = r.extrude(0.125)                                           # make prism


show_object(r)
