from build123d import *
#from ocp_vscode import show_object, reset_show


k=1000**(-3)


length, width, thickness = 80.0, 60.0, 10.0

bp = Box(length, width, thickness)

#reset_show()

show_object(bp)
#print(f"\nVolume = {res.volume*k} m³")
